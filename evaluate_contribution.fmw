FME workspace evaluate_contribution.fmw

Parameters:
- SourceDataset_PNGRASTER = $(FME_MF_DIR)samples\peter.segerstedt@sweco.se.png   # Source PNG (Portable Network Graphics) File(s)

Readers:
- PNGRASTER_1: PNGRASTER from $(SourceDataset_PNGRASTER)

PNGRASTER (reader PNGRASTER_1)
    -> Logger
Logger
    LOG_FEATURE = LOG_ONLY
    MAXCOORDS = 20
    MAXFEATS = 20
    MESSAGE = Feature is:
    SEVERITY = INFO
